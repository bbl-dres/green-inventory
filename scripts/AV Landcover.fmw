FME workspace AV Landcover.fmw

Creator_2
    GEOMTYPE = Geometry Object
    NUM = 1
    CREATED -> FeatureReader_2 [INITIATOR]
FeatureReader_2
    ATTRIBUTES = BBL_Grundstück,"id,objectid,bbl_techplz,bbl_we,bbl_teilobj,bbl_bezeichnung,bbl_portfolio,bbl_mietem,adr_land,adr_region,adr_ort,adr_plz,adr_strasse,adr_concat,wg84_lat,wg84_lon,av_egrid,bbl_status,bbl_eigentm_art,bbl_anschwrt,bbl_buchwrt,bbl_hist_gart,larea_ggf,larea_gsf,larea_uf,larea_uuf,larea_buf,larea_sealed,larea_source,bfs_gemeinde,bfs_gemeinde_nr,av_nr,av_zone_bezeichnung,av_zone_nutzung,ao_id,ao_source"
    ATTR_ACCUM_MODE = Only Use Result
    CLIP_TO_ENVELOPE = NO
    COMBINE_GEOM = Use Result
    DATASET = D:\BBL_Grundstück.geojson
    FORMAT = GEOJSON
    GEOJSON_FLATTEN_MODE = ALL_LEVELS
    GEOJSON_USE_BASENAME_AS_DEFAULT_FEATURE_TYPE = Yes
    GEOJSON_USE_SEARCH_ENVELOPE = NO
    GEOMETRY_TYPES = BBL_Grundstück,""",fme_area"""
    INITIATOR_FIRST_OUTPUT = default
    INTERACT = NONE
    ORDER_RESULTS = No
    OUTPUT_ADD_SCHEMA_ATTRIBUTES = NO
    OUTPUT_FEATURES_DISPLAY = Schema and Data Features
    BBL_Grundstück -> HTTPCaller
HTTPCaller
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api3.geo.admin.ch/rest/services/ech/MapServer/identify?geometryType=esriGeometryPoint&geometry=@Value(wg84_lon),@Value(wg84_lat)&imageDisplay=0,0,0&mapExtent=0,0,0,0&tolerance=0&layers=all:ch.swisstopo.swissboundaries3d-gemeinde-flaeche.fill,ch.swisstopo-vd.ortschaftenverzeichnis_plz&returnGeometry=false&sr=4326
    TRANSFER_TIMEOUT_LENGTH = 90
    USE_COOKIES = No
    VERIFY_SSL_CERTIFICATES = Yes
    -> JSONExtractor
JSONExtractor
    EXTRACT_QUERY_TABLE = gemname json["results"][0]["attributes"]["gemname"]
    JSON_DOCUMENT = @Value(_response_body)
    READ_FROM_FILE = NO
    EVALUATED -> TestFilter
TestFilter
    DEFAULT_VALUE = <UNFILTERED>
    PASSED_TEST_GROUP_OUTPUT = FIRST
    TEST_LIST = "BOOL_OP,OR,COMPOSITE_TEST,""""""1"""""",TEST_CLAUSE,TEST @Value(gemname) = Bern",@Value(gemname) = Bern
    @Value(gemname) = Bern -> VertexCreator
VertexCreator
    MEASURE_TYPE_LOOKUP = CONTINUOUS
    MODE = REPLACE
    REMOVE_ATTRIBUTES = No
    XVAL = @Value(wg84_lon)
    YVAL = @Value(wg84_lat)
    MEASURE_TYPE = Continuous
    MODE_NAME = Replace with Point
    -> Reprojector
Reprojector
    DEST = CH1903Plus_1.LV95/01
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> FeatureReader_3 [INITIATOR]
Note: AV Parcels / Grundstücke
FeatureReader_3
    ATTRIBUTES = cppt,"BFSNr,Kategorie,Nummer,Koordinate,Hoehe,Punktzeichen,Begehbar,Kanton,fid",dprsf,"BFSNr,NBIdent,Nummer,EGRIS_EGRID,Vollstaendigkeit,Art,Flaeche,Gueltigkeit,Kanton,fid",dprsfproj,"BFSNr,NBIdent,Nummer,EGRIS_EGRID,Vollstaendigkeit,Art,Flaeche,Kanton,fid",hadr,"BFSNr,Hausnummer,Gebaeudename,GWR_EGID,GWR_EDID,Strassenname,PLZ,Zusatzziffern,Ortschaftsname,Ori,Loc,Kanton,fid",lcobj,"BFSNr,Typ,Text,Art,Ori,Loc,Kanton,fid",lcsf,"BFSNr,Qualitaet,Art,GWR_EGID,Kanton,fid",lcsfproj,"BFSNr,Qualitaet,Art,GWR_EGID,Kanton,fid",lnna,"BFSNr,Kategorie,Name,Ori,Loc,Kanton,fid",locpos,"BFSNr,Strassenname,Ori,Loc,Kanton,fid",mbsf,"BFSNr,Name,Kanton,fid",osbp,"BFSNr,Gueltigkeit,Punktzeichen,Kanton,fid",osnr,"BFSNr,NBIdent,Nummer,Ori,Loc,Dif,Kanton,fid",osnrproj,"BFSNr,NBIdent,Nummer,Ori,Loc,Dif,Kanton,fid",plli,"BFSNr,Betreiber,Medium,Gueltigkeit,Sichtbarkeit,Kanton,fid",plna,"BFSNr,Betreiber,Ori,Loc,Kanton,fid",plsf,"BFSNr,Betreiber,Medium,Gueltigkeit,Kanton,fid",resf,"BFSNr,NBIdent,Nummer,EGRIS_EGRID,Vollstaendigkeit,Flaeche,Gueltigkeit,Kanton,fid",resfhl,"BFSNr,Kanton,fid",resfproj,"BFSNr,NBIdent,Nummer,EGRIS_EGRID,Vollstaendigkeit,Flaeche,Kanton,fid",slide,"BFSNr,NBIdent,Identifikator,Name,Gueltiger_Eintrag,Kanton,fid",slideobj,"BFSNr,NBIdent,Identifikator,Name,Ori,Loc,Kanton,fid",soli,"BFSNr,Gueltigkeit,Art,Qualitaet,Kanton,fid",soobj,"BFSNr,Typ,Text,Art,Ori,Loc,Kanton,fid",sopt,"BFSNr,Gueltigkeit,Art,Qualitaet,Ori,Kanton,fid",sosf,"BFSNr,Gueltigkeit,Art,Qualitaet,GWR_EGID,Kanton,fid",tbbp,"BFSNr,Gueltigkeit,Punktzeichen,Hoheitsgrenzpunkt,Kanton,fid",tbli,"Typ,Gueltigkeit,Kanton,fid"
    ATTR_ACCUM_MODE = Only Use Result
    COMBINE_GEOM = Use Result
    DATASET = C:\Users\DavidRasner\Downloads\av_lv95_bern\geopackage\av_2056.gpkg
    FEATURETYPES = resf
    FORMAT = OGCGEOPACKAGE
    GEOMETRY_TYPES = cppt,"""wkb_geometry,fme_point""",dprsf,"""wkb_geometry,fme_arc,fme_area,fme_collection,fme_line,fme_point,fme_solid""",dprsfproj,"""wkb_geometry,fme_area""",hadr,"""wkb_geometry,fme_point""",lcobj,"""wkb_geometry,fme_point""",lcsf,"""wkb_geometry,fme_arc,fme_area,fme_collection,fme_line,fme_point,fme_solid""",lcsfproj,"""wkb_geometry,fme_area""",lnna,"""wkb_geometry,fme_point""",locpos,"""wkb_geometry,fme_point""",mbsf,"""wkb_geometry,fme_area""",osbp,"""wkb_geometry,fme_point""",osnr,"""wkb_geometry,fme_point""",osnrproj,"""wkb_geometry,fme_point""",plli,"""wkb_geometry,fme_line""",plna,"""wkb_geometry,fme_point""",plsf,"""wkb_geometry,fme_arc,fme_area,fme_collection,fme_line,fme_point,fme_solid""",resf,"""wkb_geometry,fme_arc,fme_area,fme_collection,fme_line,fme_point,fme_solid""",resfhl,"""wkb_geometry,fme_line""",resfproj,"""wkb_geometry,fme_arc,fme_area,fme_collection,fme_line,fme_point,fme_solid""",slide,"""wkb_geometry,fme_area""",slideobj,"""wkb_geometry,fme_point""",soli,"""wkb_geometry,fme_line""",soobj,"""wkb_geometry,fme_point""",sopt,"""wkb_geometry,fme_point""",sosf,"""wkb_geometry,fme_area""",tbbp,"""wkb_geometry,fme_point""",tbli,"""wkb_geometry,fme_line"""
    INITIATOR_FIRST_OUTPUT = default
    INTERACT = WITHIN
    MAX_FEATURES = 10
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    resf -> FeatureReader [INITIATOR]
    resf -> DuplicateFilter
Note: AV Landcover / Bodenabdeckung
FeatureReader
    ATTRIBUTES = cppt,"BFSNr,Kategorie,Nummer,Koordinate,Hoehe,Punktzeichen,Begehbar,Kanton,fid",dprsf,"BFSNr,NBIdent,Nummer,EGRIS_EGRID,Vollstaendigkeit,Art,Flaeche,Gueltigkeit,Kanton,fid",dprsfproj,"BFSNr,NBIdent,Nummer,EGRIS_EGRID,Vollstaendigkeit,Art,Flaeche,Kanton,fid",hadr,"BFSNr,Hausnummer,Gebaeudename,GWR_EGID,GWR_EDID,Strassenname,PLZ,Zusatzziffern,Ortschaftsname,Ori,Loc,Kanton,fid",lcobj,"BFSNr,Typ,Text,Art,Ori,Loc,Kanton,fid",lcsf,"BFSNr,Qualitaet,Art,GWR_EGID,Kanton,fid",lcsfproj,"BFSNr,Qualitaet,Art,GWR_EGID,Kanton,fid",lnna,"BFSNr,Kategorie,Name,Ori,Loc,Kanton,fid",locpos,"BFSNr,Strassenname,Ori,Loc,Kanton,fid",mbsf,"BFSNr,Name,Kanton,fid",osbp,"BFSNr,Gueltigkeit,Punktzeichen,Kanton,fid",osnr,"BFSNr,NBIdent,Nummer,Ori,Loc,Dif,Kanton,fid",osnrproj,"BFSNr,NBIdent,Nummer,Ori,Loc,Dif,Kanton,fid",plli,"BFSNr,Betreiber,Medium,Gueltigkeit,Sichtbarkeit,Kanton,fid",plna,"BFSNr,Betreiber,Ori,Loc,Kanton,fid",plsf,"BFSNr,Betreiber,Medium,Gueltigkeit,Kanton,fid",resf,"BFSNr,NBIdent,Nummer,EGRIS_EGRID,Vollstaendigkeit,Flaeche,Gueltigkeit,Kanton,fid",resfhl,"BFSNr,Kanton,fid",resfproj,"BFSNr,NBIdent,Nummer,EGRIS_EGRID,Vollstaendigkeit,Flaeche,Kanton,fid",slide,"BFSNr,NBIdent,Identifikator,Name,Gueltiger_Eintrag,Kanton,fid",slideobj,"BFSNr,NBIdent,Identifikator,Name,Ori,Loc,Kanton,fid",soli,"BFSNr,Gueltigkeit,Art,Qualitaet,Kanton,fid",soobj,"BFSNr,Typ,Text,Art,Ori,Loc,Kanton,fid",sopt,"BFSNr,Gueltigkeit,Art,Qualitaet,Ori,Kanton,fid",sosf,"BFSNr,Gueltigkeit,Art,Qualitaet,GWR_EGID,Kanton,fid",tbbp,"BFSNr,Gueltigkeit,Punktzeichen,Hoheitsgrenzpunkt,Kanton,fid",tbli,"Typ,Gueltigkeit,Kanton,fid"
    ATTR_ACCUM_MODE = Merge Initiator and Result
    ATTR_CONFLICT_RES = Use Result
    ATTR_IGNORE_NULLS = No
    CLIP_TO_ENVELOPE = NO
    COMBINE_GEOM = Use Result
    DATASET = C:\Users\DavidRasner\Downloads\av_lv95_bern\geopackage\av_2056.gpkg
    FEATURETYPES = lcsf
    FORMAT = OGCGEOPACKAGE
    GEOMETRY_TYPES = cppt,"""wkb_geometry,fme_point""",dprsf,"""wkb_geometry,fme_arc,fme_area,fme_collection,fme_line,fme_point,fme_solid""",dprsfproj,"""wkb_geometry,fme_area""",hadr,"""wkb_geometry,fme_point""",lcobj,"""wkb_geometry,fme_point""",lcsf,"""wkb_geometry,fme_arc,fme_area,fme_collection,fme_line,fme_point,fme_solid""",lcsfproj,"""wkb_geometry,fme_area""",lnna,"""wkb_geometry,fme_point""",locpos,"""wkb_geometry,fme_point""",mbsf,"""wkb_geometry,fme_area""",osbp,"""wkb_geometry,fme_point""",osnr,"""wkb_geometry,fme_point""",osnrproj,"""wkb_geometry,fme_point""",plli,"""wkb_geometry,fme_line""",plna,"""wkb_geometry,fme_point""",plsf,"""wkb_geometry,fme_arc,fme_area,fme_collection,fme_line,fme_point,fme_solid""",resf,"""wkb_geometry,fme_arc,fme_area,fme_collection,fme_line,fme_point,fme_solid""",resfhl,"""wkb_geometry,fme_line""",resfproj,"""wkb_geometry,fme_arc,fme_area,fme_collection,fme_line,fme_point,fme_solid""",slide,"""wkb_geometry,fme_area""",slideobj,"""wkb_geometry,fme_point""",soli,"""wkb_geometry,fme_line""",soobj,"""wkb_geometry,fme_point""",sopt,"""wkb_geometry,fme_point""",sosf,"""wkb_geometry,fme_area""",tbbp,"""wkb_geometry,fme_point""",tbli,"""wkb_geometry,fme_line"""
    INITIATOR_FIRST_OUTPUT = default
    INTERACT = INTERSECTS
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    lcsf -> Deaggregator
Deaggregator
    ATTR_ACCUM_MODE = HANDLE_CONFLICT
    ATTR_CONFLICT_RES = Use List Attribute Values
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> Dissolver
Dissolver
    ACCUM_INPUT_ATTRS_LOOKUP = One
    CLEANING_TOLERANCE_LOOKUP = AUTO
    CONNECT_Z_MODE_LOOKUP = FIRST_WINS
    DEAGGREGATE_INPUT = Yes
    GROUP_BY = fid
    ACCUM_INPUT_ATTRS = Use Attributes From One Feature
    CLEANING_TOLERANCE = Automatic
    CONNECT_Z_MODE = First Wins
    AREA -> Clipper [CANDIDATE]
DuplicateFilter
    INPUT_ORDERED_CHOICE_LOOKUP = NO
    KEYATTR = EGRIS_EGRID
    INPUT_ORDERED_CHOICE = No
    UNIQUE -> Deaggregator_2
Deaggregator_2
    ATTR_ACCUM_MODE = HANDLE_CONFLICT
    ATTR_CONFLICT_RES = Use List Attribute Values
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> Dissolver_2
Dissolver_2
    ACCUM_INPUT_ATTRS_LOOKUP = One
    CLEANING_TOLERANCE_LOOKUP = AUTO
    CONNECT_Z_MODE_LOOKUP = FIRST_WINS
    DEAGGREGATE_INPUT = Yes
    GROUP_BY = fid
    ACCUM_INPUT_ATTRS = Use Attributes From One Feature
    CLEANING_TOLERANCE = Automatic
    CONNECT_Z_MODE = First Wins
    AREA -> Clipper [CLIPPER]
    AREA -> BulkAttributeRenamer_2
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> GeographicAreaCalculator
Note: area_polygon_m2
GeographicAreaCalculator
    AREA_ATTR = area_polygon_m2
    AreaMult = 1
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(area_polygon_m2) <= 2",@Value(area_polygon_m2) < 0.1
    <UNFILTERED> -> Reprojector_2
Note: LV95 to WGS84
Reprojector_2
    DEST = LL-WGS84
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeCreator
    REPROJECTED -> TestFilter_3
AttributeCreator
    -> FeatureWriter_3 [Output]
Note: Upsert / source_fid
FeatureWriter_3
    DATASET = Supabase Dav
    DATASET_ATTR = _dataset
    FEATURE_TYPE_LIST_ATTR = _feature_types
    FORMAT = POSTGIS
    POSTGIS_ALWAYS_CREATE_FEATURE_TYPES = NO
    POSTGIS_BULK_COPY = YES
    POSTGIS_CASE_CONTROL_ATTR_NAMES = lower
    POSTGIS_CASE_CONTROL_FT_NAMES = none
    POSTGIS_COORDINATE_SYSTEM_GRANULARITY = FEATURE_TYPE
    POSTGIS_GENERIC_GEOMETRY = yes
    POSTGIS_NAMED_CONNECTION = Supabase Dav
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
Note: Gebäude
TestFilter_3
    DEFAULT_VALUE = <UNFILTERED>
    PASSED_TEST_GROUP_OUTPUT = FIRST
    TEST_LIST:
      "BOOL_OP,OR,COMPOSITE_TEST,""""""1"""""",TEST_CLAUSE,TEST @Value(Art) = Gebaeude",Buildings,"BOOL_OP,OR,COMPOSITE_TEST,""""""1 OR 2 OR 3"""""",TEST_CLAUSE,TEST @Value(Art) = Trottoir
      TEST @Value(Art) = Strasse_Weg
      TEST @Value(Art) = uebrige_befestigte",Surfaces,"BOOL_OP,OR,COMPOSITE_TEST,""""""1"""""",TEST_CLAUSE,TEST @Value(Art) = Gartenanlage",Garden,"BOOL_OP,OR,COMPOSITE_TEST,""""""1 OR 2"""""",TEST_CLAUSE,TEST @Value(Art) = Wasserbecken
      TEST @Value(Art) = Gewaesser_fliessendes",Gewässer
    Buildings -> BulkAttributeRenamer
    Surfaces -> BulkAttributeRenamer_3
    Garden -> BulkAttributeRenamer_4
BulkAttributeRenamer
    ATTRCHOICE_ACTION = NONPROTECTEDFME
    MODE_CHOICE = RENAME
    PATTERN_ACTION_DISP = ADDPREFIX
    REPLACE_STR = REMOVE_
    ATTRCHOICE = All Attributes
    -> AttributeCreator_2
AttributeCreator_2
    ATTR_TABLE:
      SET_TO buildingId (varchar(200))
      SET_TO siteId (varchar(200))
      SET_TO name (varchar(200))
      SET_TO primaryTypeOfBuilding (varchar(200))
      SET_TO secondaryTypeOfBuilding (varchar(200))
      SET_TO typeOfOwnership (varchar(200))
      SET_TO validFrom (varchar(200))
      SET_TO validUntil (varchar(200))
      SET_TO constructionYear (varchar(200))
      SET_TO buildingPermitDate (varchar(200))
      SET_TO yearOfLastRefurbishment (varchar(200))
      SET_TO parkingSpaces (varchar(200))
      SET_TO electricVehicleChargingStations (varchar(200))
      SET_TO monumentProtection (varchar(200))
      SET_TO status (varchar(200))
      SET_TO energyEfficiencyClass (varchar(200))
      SET_TO streetName (varchar(200))
      SET_TO houseNumber (varchar(200))
      SET_TO postalCode (varchar(200))
      SET_TO city (varchar(200))
      SET_TO stateProvincePrefecture (varchar(200))
      SET_TO country (varchar(200))
      SET_TO extensionData.numberOfFloors (varchar(200))
      SET_TO extensionData.responsiblePerson (varchar(200))
      SET_TO extensionData.egid (varchar(200))
      SET_TO extensionData.egrid (varchar(200))
      SET_TO extensionData.portfolio (varchar(200))
      SET_TO extensionData.portfolioGroup (varchar(200))
      SET_TO extensionData.heatingGenerator (varchar(200))
      SET_TO extensionData.heatingSource (varchar(200))
      SET_TO extensionData.hotWater (varchar(200))
      SET_TO extensionData.plotName (varchar(200))
      SET_TO extensionData.plotId (varchar(200))
      SET_TO extensionData.netFloorArea (varchar(200))
      SET_TO legacyId (varchar(200))
    -> AttributeRemover
AttributeRemover
    REMOVE_ATTRS = REMOVE_Art,REMOVE_BFSNr,REMOVE_EGRIS_EGRID,REMOVE_Flaeche,REMOVE_GWR_EGID,REMOVE_Gueltigkeit,REMOVE_Kanton,REMOVE_NBIdent,REMOVE_Nummer,REMOVE_Qualitaet,REMOVE_Vollstaendigkeit,REMOVE__clipped,REMOVE__geometry_label,REMOVE__part_number,REMOVE_area_polygon_m2,REMOVE_fid
    -> FeatureWriter_2 [Output]
Note: buildings.geojson
FeatureWriter_2
    DATASET = C:\Users\DavidRasner\Documents\GitHub\green-inventory\data\buildings.geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
BulkAttributeRenamer_3
    ATTRCHOICE_ACTION = NONPROTECTEDFME
    MODE_CHOICE = RENAME
    PATTERN_ACTION_DISP = ADDPREFIX
    REPLACE_STR = REMOVE_
    ATTRCHOICE = All Attributes
    -> AttributeCreator_4
AttributeCreator_4
    ATTR_TABLE:
      SET_TO surfaceId (varchar(200))
      SET_TO siteId (varchar(200))
      SET_TO name (varchar(200))
      SET_TO surfaceType (varchar(200))
      SET_TO careProfileId (varchar(200))
      SET_TO areaM2 (varchar(200))
      SET_TO condition (varchar(200))
      SET_TO material (varchar(200))
      SET_TO thicknessCm (varchar(200))
      SET_TO drainageType (varchar(200))
      SET_TO lastCareDate (varchar(200))
      SET_TO notes (varchar(200))
      SET_TO validFrom (varchar(200))
      SET_TO validUntil (varchar(200))
      SET_TO createdAt (varchar(200))
      SET_TO updatedAt (varchar(200))
      SET_TO eventType (varchar(200))
    -> AttributeRemover_3
AttributeRemover_3
    REMOVE_ATTRS = REMOVE__clipped,REMOVE__geometry_label,REMOVE__part_number,REMOVE_area_polygon_m2,REMOVE_Art,REMOVE_BFSNr,REMOVE_EGRIS_EGRID,REMOVE_fid,REMOVE_Flaeche,REMOVE_Gueltigkeit,REMOVE_GWR_EGID,REMOVE_Kanton,REMOVE_NBIdent,REMOVE_Nummer,REMOVE_Qualitaet,REMOVE_Vollstaendigkeit
    -> FeatureWriter_5 [Output]
Note: surfaces.geojson
FeatureWriter_5
    DATASET = C:\Users\DavidRasner\Documents\GitHub\green-inventory\data\surfaces.geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
BulkAttributeRenamer_4
    ATTRCHOICE_ACTION = NONPROTECTEDFME
    MODE_CHOICE = RENAME
    PATTERN_ACTION_DISP = ADDPREFIX
    REPLACE_STR = REMOVE_
    ATTRCHOICE = All Attributes
    -> AttributeCreator_5
AttributeCreator_5
    ATTR_TABLE:
      SET_TO gardenId (varchar(200))
      SET_TO siteId (varchar(200))
      SET_TO name (varchar(200))
      SET_TO gardenType (varchar(200))
      SET_TO careProfileId (varchar(200))
      SET_TO areaM2 (varchar(200))
      SET_TO condition (varchar(200))
      SET_TO designPeriod (varchar(200))
      SET_TO heritageStatus (varchar(200))
      SET_TO originalDesigner (varchar(200))
      SET_TO keyFeatures (varchar(200))
      SET_TO historicRoseVarieties (varchar(200))
      SET_TO irrigated (varchar(200))
      SET_TO lastCareDate (varchar(200))
      SET_TO notes (varchar(200))
      SET_TO validFrom (varchar(200))
      SET_TO validUntil (varchar(200))
      SET_TO createdAt (varchar(200))
      SET_TO updatedAt (varchar(200))
      SET_TO eventType (varchar(200))
    -> AttributeRemover_4
AttributeRemover_4
    REMOVE_ATTRS = REMOVE__clipped,REMOVE__geometry_label,REMOVE__part_number,REMOVE_area_polygon_m2,REMOVE_Art,REMOVE_BFSNr,REMOVE_EGRIS_EGRID,REMOVE_fid,REMOVE_Flaeche,REMOVE_Gueltigkeit,REMOVE_GWR_EGID,REMOVE_Kanton,REMOVE_NBIdent,REMOVE_Nummer,REMOVE_Qualitaet,REMOVE_Vollstaendigkeit
    -> FeatureWriter_6 [Output]
Note: gardens.geojson
FeatureWriter_6
    DATASET = C:\Users\DavidRasner\Documents\GitHub\green-inventory\data\gardens.geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
BulkAttributeRenamer_2
    ATTRCHOICE_ACTION = NONPROTECTEDFME
    MODE_CHOICE = RENAME
    PATTERN_ACTION_DISP = ADDPREFIX
    REPLACE_STR = REMOVE_
    ATTRCHOICE = All Attributes
    -> AttributeCreator_3
AttributeCreator_3
    ATTR_TABLE:
      SET_TO parcelId (varchar(200))
      SET_TO buildingId (varchar(200))
      SET_TO plotNumber (varchar(200))
      SET_TO name (varchar(200))
      SET_TO municipality (varchar(200))
      SET_TO canton (varchar(200))
      SET_TO area (varchar(200))
      SET_TO landUseZone (varchar(200))
      SET_TO ownershipType (varchar(200))
    -> AttributeRemover_2
AttributeRemover_2
    REMOVE_ATTRS = REMOVE__geometry_label,REMOVE__part_number,REMOVE_BFSNr,REMOVE_EGRIS_EGRID,REMOVE_fid,REMOVE_Flaeche,REMOVE_Gueltigkeit,REMOVE_Kanton,REMOVE_NBIdent,REMOVE_Nummer,REMOVE_Vollstaendigkeit
    -> FeatureWriter_4 [Output]
Note: parcels.geojson
FeatureWriter_4
    DATASET = C:\Users\DavidRasner\Documents\GitHub\green-inventory\data\parcels.geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
